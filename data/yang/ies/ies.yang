module ies {
    namespace "http://www.nokia.com/management-solutions/ies";
    yang-version 1.1;
    prefix "ies";
    import ietf-inet-types { prefix "inet-types"; }
    import qos-filter-common { prefix "qos-filter-common"; }
    import sap-common { prefix "sap-common"; }
    import svc-common { prefix "svc-common"; }
    import ip-transport-common { prefix "ip-transport-common"; }

    organization        "NOKIA Corp";
    contact "";
    description "";
    revision "2023-06-27" {
        description
            "23.11 changes - ip-transport support";
    }
    revision "2021-11-05" {
        description
                "Initial revision.";
    }

    typedef ipv4-address {
        type inet-types:ipv4-address-no-zone {
            pattern "[0-9\\.]*";
            pattern "(([0-9]|[1-9][0-9]|1[0-9][0-9]|2[0-4][0-9]|25[0-5])\\.){3}([0-9]|[1-9][0-9]|1[0-9][0-9]|2[0-4][0-9]|25[0-5])(%[\\p{N}\\p{L}]+)?";
        }
        description "An IPv4 address.";
    }

    grouping vrrp-details {
        leaf virtual-router-id {
            type int32 {
                range "1..255";
            }
            mandatory true;
            description "Virtual Router Identifier (VRID) for the VRRP virtual router instance";
        }

        leaf-list backup {
            type ipv4-address;
            max-elements 16;
            description "Virtual router IP addresses for the interface";
        }

        leaf priority {
            type uint32 {
                range "1..255";
            }
            description "Base priority for the VRRP";
        }

        leaf mac {
            type string {
                pattern "([0-9a-fA-F]{2}(:[0-9a-fA-F]{2}){5})|([0-9a-fA-F]{2}(-[0-9a-fA-F]{2}){5})";
            }
            description "MAC address used by virtual router instance overriding the VRRP default derived from the VRID";
        }

        leaf ping-reply {
            type boolean;
            description "Allow non-owner master to reply to ICMP echo requests";
        }
    }


    grouping configuration-details {
        container ies {
            uses svc-common:svc-details;

            leaf ne-service-id {
                type uint32 {
                    range "1..2147483647";
                }
                description "Specify Service Id";
            }

            container site-details{
                list site {
                    key "device-id";

                    uses svc-common:site-details;

                    list interface {
                        key "interface-name";
                        description "Interface parameters";

                        leaf interface-name {
                            type string;
                            description "Name of the interface";
                        }

                        leaf interface-type {
                            type enumeration {
                                enum sap;
                                enum sdp;
                                enum loopback;
                            }
                            description "Name of the interface";
                            default sap;
                        }

                        leaf admin-state {
                            type enumeration {
                                enum unlocked;
                                enum locked;
                            }
                            description "Service Administrative State.";
                        }

                        leaf ip-mtu {
                            type uint16;
                            description "ip mtu";
                        }

                        container ipv4 {
                            container primary {
                                description "Enter the primary context";

                                leaf address {
                                    type ipv4-address;
                                    mandatory true;
                                    description "Primary IPv4 address assigned to the interface";
                                }

                                leaf prefix-length {
                                    type uint32 {
                                        range "0..32";
                                    }
                                    mandatory true;
                                    description "IPv4 address prefix length";
                                }
                            }

                            list secondary {
                                key "address";
                                description "Enter the secondary list instance";

                                leaf address {
                                    type ipv4-address;
                                    mandatory true;
                                    description "Secondary IPv4 address assigned to the interface";
                                }

                                leaf prefix-length {
                                    type uint32 {
                                        range "0..32";
                                    }
                                    mandatory true;
                                    description "IPv4 address prefix length";
                                }
                            } // list secondary

                            list vrrp {
                                key "virtual-router-id";
                                uses ies:vrrp-details;
                            }
                        } // container ipv4

                        container ipv6-details {
                            list ipv6 {
                                key "ipv6-address";
                                description "Enter the address list instance";

                                leaf ipv6-address {
                                    type inet-types:ipv6-address-no-zone;
                                    mandatory true;
                                    description "IPv6 address assigned to the interface";
                                }

                                leaf prefix-length {
                                    type uint32 {
                                        range "0..128";
                                    }
                                    mandatory true;
                                    description "IPv6 address prefix length";
                                }
                            }  // list of address

                            list vrrp {
                                key "virtual-router-id";
                                uses ies:vrrp-details;
                            }
                        }

                        container spoke-sdp {
                            when "../interface-type= 'sdp' ";
                            description "IES spoke SDP information";

                             leaf admin-state {
                                type enumeration {
                                     enum unlocked;
                                     enum locked;
                                }
                                default unlocked;
                                description "The desired state of this Service-SDP binding.";
                            }

                            leaf destination-device-id {
                                type string;
                                description "SDP Destination Device Id (optional - UI rendering)";
                            }

                            leaf steering-parameter {
                                type string;
                                description "Steering parameter used by Service Fulfillment";
                            }

                            leaf sdp-id {
                                type string;
                                description "SDP identifier xPath";
                            }

                            leaf vc-id {
                                type uint32 {
                                    range "1..4294967295";
                                }
                                description "SDP virtual circuit identifier";
                            }

                            leaf description {
                                type string;
                                description "User-provided description for the SDP Bind";
                            }

                            leaf collect-stats {
                                type boolean;
                                default "false";
                                description "Allow agent to collect accounting statistics";
                            }

                            leaf accounting-policy-id {
                                type int32 {
                                range "1..99";
                                }
                                description "The unique identifier for the Accounting policy.";
                            }

                        } // container spoke-sdp

                        container sap {
                            when "../interface-type= 'sap' ";
                            description "Interface service access point";
                            uses sap-common:sap-details;
                            uses qos-filter-common:access-configuration-details;
                        } // container of sap

                        container vpls {
                            description "Enter the vpls list instance";
                            leaf vpls-name {
                                type string;
                                description "VPLS service";
                            }
                        }

                    } // list of interface
                    container ip-transports {
                        list ip-transport {
                            key "transport-port-id";
                            uses ip-transport-common:ip-transport-details;
                        } // // list of ip-transport
                    }
                } // list of site
            }
        } // ies
    }

    uses ies:configuration-details;
}
