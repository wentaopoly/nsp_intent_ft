module evpn-epipe {
    namespace "http://www.nokia.com/management-solutions/evpn-epipe";
    yang-version 1.1;
    prefix "evpn-epipe";
    import qos-filter-common { prefix "qos-filter-common"; }
    import sap-common { prefix "sap-common"; }
    import svc-common { prefix "svc-common"; }
    organization "NOKIA Corp";
    contact "";
    description "";
    revision "2024-08-21" {
        description
            "evi range change";
    }
    revision "2023-01-02" {
        description
            "23.4 changes - adding local/remote eth tags manmandatory";
    }
    revision "2022-05-02" {
            description
                    "22.6 changes - adding back when clause";
    }
    revision "2021-09-02" {
        description
                "21.11 changes";
    }
    revision "2021-04-26" {
        description
                "Initial revision.";
    }
    typedef ieee-address {
        type string {
            pattern "([0-9a-fA-F]{2}(:[0-9a-fA-F]{2}){5})|([0-9a-fA-F]{2}(-[0-9a-fA-F]{2}){5})";
        }
        description "The ieee-address type represents an IEEE 802 MAC address.";
    }
    
    typedef rt-type {
        type enumeration {
    	    enum unspecified;
            enum imp;
            enum exp;
            enum import-export;
        }
    }
    
    typedef resolve-status {
        type enumeration {
            enum "none"                         { value 0; }
            enum "filter"                       { value 1; }
            enum "any"                          { value 2; }
        }
        description "The TResolveStatus indicates resolution status of the tunnels.";
    }
    
    typedef string-not-all-spaces {
        type string {
            pattern "(.*\\S.*)|()" {
                error-message "The given string must not be all spaces.";
            }
        }
    }
    
    typedef named-item {
        type string-not-all-spaces {
            length "1..32";
        }
        description "Named item used for naming instances of entities.";
    }

    grouping bgp-details {
        leaf route-distinguisher {
            type string;
            description "Route distinguisher";
        }

        leaf-list vsi-import {
            type string;
            max-elements 5;
            ordered-by user;
            description "VSI import policies";
        }

        leaf-list vsi-export {
            type string;
            max-elements 5;
            ordered-by user;
            description "VSI export policies";
        }

        list route-target {
            key "target-type target-value";
            description "Enter the vrf-target context";

            leaf target-type {
                type rt-type;
                description "The type of route target";
            }

            leaf target-value {
                type string;
                description "The route target value";
            }
        } // list route-target
    }

    grouping site-details {

        leaf evi {
            type uint32 {
                range "1..16777215";
            }
            description "EVPN ID";
        }

        leaf ecmp {
            type int32 {
                range "1..32";
            }
            description "Maximum ECMP routes information";
        }

        container local-ac {
            description "Enter the local-ac context";

            leaf name {
                type named-item;
                mandatory false;
                description "Attachment circuit name";
            }

            leaf eth-tag {
                type int32 {
                    range "1..16777215";
                }
                mandatory false;
                description "Ethernet tag of the attachment circuit";
            }

        } // container local-ac

        container remote-ac {
            description "Enter the remote-ac context";

            leaf name {
                type named-item;
                mandatory false;
                description "Attachment circuit name";
            }

            leaf eth-tag {
                type int32 {
                    range "1..16777215";
                }
                mandatory false;
                description "Ethernet tag of the attachment circuit";
            }

        } // container remote-ac


        container vxlan {
            when "../../evpn-type = 'vxlan' ";
            container bgp-instance {
                uses evpn-epipe:bgp-details;
            }

            leaf vni {
                type uint32;
                description "VNI of the VXLAN";
            }
        }

        container mpls {
            when "../../evpn-type = 'mpls' ";
            container bgp-instance {
                uses evpn-epipe:bgp-details;
            }

            leaf force-vc-forwarding {
                type enumeration {
                    enum "vlan"                         { value 1; }
                    enum "qinq-c-tag-c-tag"             { value 2; }
                    enum "qinq-s-tag-c-tag"             { value 3; }
                }
                description "VC forwarding action";
            }

            leaf control-word {
                type boolean;
                description "Enable control word support";
            }

            container auto-bind-tunnel {
                description "Enter the auto-bind-tunnel context";

                leaf resolution {
                    type resolve-status;
                    description "Resolution method for tunnel selection";
                }

                leaf enforce-strict-tunnel-tagging {
                    type boolean;
                    description "Consider only LSPs marked with an admin-tag for next-hop resolution";
                }

                container resolution-filter {
                    description "Enter the resolution-filter context";

                    leaf bgp {
                        type boolean;
                        description "Set BGP type for auto bind tunnel";
                    }

                    leaf gre {
                        type boolean;
                        description "Enable/disable setting GRE type for auto-bind-tunnel";
                    }

                    leaf ldp {
                        type boolean;
                        description "Enable/disable setting LDP type for auto-bind-tunnel";
                    }

                    leaf rsvp {
                        type boolean;
                        description "Enable/disable setting RSVP-TE type for auto-bind-tunnel";
                    }

                    leaf sr-isis {
                        type boolean;
                        description "Enable/disable setting SR-ISIS type for auto-bind-tunnel";
                    }

                    leaf sr-ospf {
                        type boolean;
                        description "Enable/disable setting SR-OSPF type for auto-bind-tunnel";
                    }

                    leaf sr-te {
                        type boolean;
                        description "Enable/disable setting SR-TE type for auto-bind-tunnel";
                    }

                } // container resolution-filter

            } // container auto-bind-tunnel
        }

        container sap-details {
            list sap {
                 key "port-id inner-vlan-tag outer-vlan-tag";
                 max-elements 2;
                 uses sap-common:sap-details;
                 uses qos-filter-common:access-configuration-details;
            }
        }

         container multi-homing-site-details {
            leaf device-id {
                 type string;
                 description "NE Id";
            }

            leaf route-distinguisher {
                 type string;
                 description "Route distinguisher";
            }

            uses sap-common:sap-details;
         }
    }

    grouping configuration-details {
        container evpn-epipe {
            uses svc-common:svc-details;

            leaf ne-service-id {
                type uint32 {
                    range "1..2147483647";
                }
                description "Specify NE Service Id";
            }
            
            leaf mtu {
                type uint16;
                description "svc mtu";
            }

            leaf evpn-type {
                type enumeration {
                    enum mpls                   { value 0; }
                    enum vxlan                  { value 1; }
                }
                description "EVPN Type";
            }
            
            container site-a {
                uses svc-common:site-details;
                uses evpn-epipe:site-details;
            }

            container site-b {
                uses svc-common:site-details;
                uses evpn-epipe:site-details;
            }
        }
    }
    uses evpn-epipe:configuration-details;
}
