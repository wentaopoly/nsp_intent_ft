module etree {
    namespace "http://www.nokia.com/management-solutions/etree";
    yang-version 1.1;
    prefix "etree";
    import qos-filter-common { prefix "qos-filter-common"; }
    import vpls-eth-cfm-common { prefix "vpls-eth-cfm-common"; }
    import sdp-binding-common { prefix "sdp-binding-common"; }
    import sap-common { prefix "sap-common"; }
    import svc-common { prefix "svc-common"; }
    import ietf-inet-types { prefix "inet-types"; }
    organization "NOKIA Corp";
    contact "";
    description "";
    revision "2024-08-26" {
        description "24.8 changes";
    }
    revision "2023-07-20" {
        description
            "23.11 changes";
    }
    revision "2021-08-25" {
        description
                "21.11 changes";
    }
    revision "2021-04-18" {
        description
                "Initial revision.";
    }
    typedef ieee-address {
        type string {
            pattern "([0-9a-fA-F]{2}(:[0-9a-fA-F]{2}){5})|([0-9a-fA-F]{2}(-[0-9a-fA-F]{2}){5})";
        }
        description "The ieee-address type represents an IEEE 802 MAC address.";
    }
    typedef ipv4-address {
        type inet-types:ipv4-address-no-zone {
            pattern "[0-9\\.]*";
            pattern "(([0-9]|[1-9][0-9]|1[0-9][0-9]|2[0-4][0-9]|25[0-5])\\.){3}([0-9]|[1-9][0-9]|1[0-9][0-9]|2[0-4][0-9]|25[0-5])(%[\\p{N}\\p{L}]+)?";
        }
        description "An IPv4 address.";
    }

    grouping configuration-details {
        container etree {
            leaf ne-service-id {
                type uint32 {
                    range "1..2147483647";
                }
                description "Specify NE Service Id";
            }

            leaf mtu {
                type uint16;
                description "Service MTU";
            }

            uses svc-common:svc-details;

            container site-details{
                list site {
                    key "device-id";

                    uses svc-common:site-details;
                    container mac-flush {
                        description "Enter the mac-flush context";

                        container tldp {
                            description "Enter the tldp context";

                            leaf propagate {
                                type boolean;
                                description "Propagate MAC flush messages received from the T-LDP";
                            }

                            leaf send-on-failure {
                                type boolean;
                                description "Send MAC withdraw message on SAP/Spoke-SDP failure";
                            }

                        } // container tldp

                    } // container mac-flush
                    container fdb {
                        description "Enter the fdb context";

                        leaf discard-unknown {
                            type boolean;
                            description "Discard packets with unknown destination MAC addresses";
                        }

                        container table {
                            description "Enter the table context";

                            leaf high-wmark {
                                type int32 {
                                    range "0..100";
                                }
                                description "High watermark for the FDB table";
                            }

                            leaf low-wmark {
                                type int32 {
                                    range "0..100";
                                }
                                description "Low watermark for the FDB table";
                            }

                            leaf size {
                                type int32 {
                                    range "1..511999";
                                }
                                description "Maximum MAC entries in the FDB";
                            }

                        } // container table

                        container mac-learning {
                            description "Enter the mac-learning context";

                            leaf learning {
                                type boolean;
                                description "Enable learning of new MAC addresses";
                            }

                            leaf aging {
                                type boolean;
                                description "Enable aging of MAC addresses";
                            }

                            leaf local-age-time {
                                type int32 {
                                    range "60..86400";
                                }
                                description "Aging time for locally learned MAC addresses";
                            }

                            leaf remote-age-time {
                                type int32 {
                                    range "60..86400";
                                }
                                description "Aging time for locally learned MAC addresses";
                            }

                        } // container mac-learning
                    } // container fdb

                    list split-horizon-group {
                        key "shg-name";
                        leaf shg-name {
                            type string;
                            description "SHG name to which the SDP belongs";
                        }

                        leaf description {
                            type string;
                            description "Text description";
                        }

                        container fdb {
                            description "Enter the fdb context";

                            container saps {
                                description "Enter the saps context";

                                leaf discard-unprotected-dest-mac {
                                    type boolean;
                                    description "Discard packet with unprotected destination MAC address";
                                }
                            }
                        }
                    }

                    container igmp-snooping {
                        leaf admin-state {
                            type enumeration {
                                enum unlocked;
                                enum locked;
                            }
                            description "Administrative state of snooping.";
                        }
                        leaf report-source-address {
                            type ipv4-address;
                            description "Source IP address used when generating IGMP reports";
                        }
                        leaf query-source-address {
                            type union {
                                type enumeration {
                                    enum "system"                       { value 1; }
                                }
                                type ipv4-address;
                            }
                            description "Source address for IGMP queries";
                        }
                    }

                    list sap {
                        key "port-id inner-vlan-tag outer-vlan-tag";

                        leaf root-leaf-tag-value {
                            type int32 {
                                range "1..4094";
                            }
                            description "Leaf tag value";
                        }

                        leaf etree-leaf {
                            type boolean;
                            default "false";
                            description "Enable etree leaf access-circuit status";
                        }

                        uses sap-common:sap-details;
                        uses qos-filter-common:access-configuration-details;

                        leaf split-horizon-group {
                            type leafref {
                                path "../../split-horizon-group/shg-name";
                            }
                            description "Name of the split horizon group where the spoke SDP bind belongs to";
                        }

                        container fdb {
                            description "Enter the fdb context";

                            leaf maximum-mac-addresses {
                                type int32 {
                                    range "1..511999";
                                }
                                description "Maximum number of MAC entries in the FDB";
                            }

                            leaf discard-unknown-source {
                                type boolean;
                                description "Discard frames with unknown source";
                            }

                            leaf mac-pinning {
                                type boolean;
                                description "Enable MAC address pinning on this SAP";
                            }

                            leaf auto-learn-mac-protect {
                                type boolean;
                                description "Enable automatic update of MAC protect list";
                            }

                            container mac-learning {
                                description "Enter the mac-learning context";

                                leaf learning {
                                    type boolean;
                                    description "Enable learning of new MAC addresses";
                                }

                                leaf aging {
                                    type boolean;
                                    description "Enable aging of MAC addresses";
                                }
                            }//container mac-learning

                        } // fdb

                        container dhcp {

                            leaf admin-state {
                                type enumeration {
                                    enum unlocked;
                                    enum locked;
                                }
                                description "Administrative state of DHCP";
                            }

                            leaf snoop {
                                type boolean;
                                description "Enable DHCP snooping on the SAP";
                            }

                            container lease-populate {
                                description "Enter the lease-populate context";

                                leaf max-leases {
                                    type uint32 {
                                        range "0..131071";
                                    }
                                    description "Maximum number of DHCPv4 leases";
                                }

                            } // container lease-populate
                        }

                        leaf anti-spoof {
                            type enumeration {
                                enum "source-ip-addr"               { value 1; }
                                enum "source-mac-addr"              { value 2; }
                                enum "source-ip-and-mac-addr"       { value 3; }
                                enum "next-hop-ip-and-mac-addr"     { value 4; }
                            }
                            description "Type of anti-spoof filtering";
                        }

                        leaf oper-group {
                            type string;
                            description "Operational group";
                        }

                        container igmp-snooping {
                            leaf import-policy {
                                type string;
                                description "Import policy that filters IGMP packets";
                            }

                            leaf maximum-number-groups {
                                type uint32 {
                                    range "1..16000";
                                }
                                description "Maximum groups allowed";
                            }

                            leaf send-queries {
                                type boolean;
                                description "Generate IGMP general queries";
                            }

                            container mcac {
                                description "Enter the mcac context";
                                leaf policy {
                                    type string;
                                    description "Multicast CAC policy name";
                                }
                                container bandwidth {
                                    description "Enter the bandwidth context";

                                    leaf total {
                                        type union {
                                            type int32 {
                                                range "0..max";
                                            }
                                            type enumeration {
                                                enum "unlimited"                    { value -1; }
                                            }
                                        }
                                        description "Maximum allowed bandwidth";
                                    }

                                    leaf mandatory {
                                        type union {
                                            type int32 {
                                                range "0..max";
                                            }
                                            type enumeration {
                                                enum "unlimited"                    { value -1; }
                                            }
                                        }
                                        description "Pre-reserved bandwidth for all mandatory channels";
                                    }

                                } // container bandwidth
                            }

                            container static {
                                description "Enter the static context";

                                list group {
                                    key "group-address";
                                    description "Enter the group list instance";

                                    leaf group-address {
                                        type ipv4-address;
                                        description "Group address of static IGMP multicast channel";
                                    }

                                    choice source-or-starg {
                                        mandatory true;
                                        case source {
                                            list source {
                                                key "source-address";
                                                description "Add a list entry for source";
                                                leaf source-address {
                                                    type ipv4-address;
                                                    description "Source IP address of multicast channel sending data";
                                                }
                                            } // list source
                                        }
                                        case starg {
                                            leaf starg {
                                                type empty;
                                                description "any source address (*,G)";
                                            }
                                        }
                                    }
                                }
                            }
                        }
                    }

                    container mep {
                         uses vpls-eth-cfm-common:mep-configuration-details;
                    }
                }
            }

            container sdp-details{
                list sdp {
                    key "source-device-id sdp-id";
                    description "VPLS mesh SDP information";

                    leaf etree-root-leaf-tag {
                        type boolean;
                        default "false";
                        description "E-tree root leaf tag status";
                    }

                    leaf etree-leaf {
                        type boolean;
                        default "false";
                        description "Enable etree leaf access-circuit status";
                    }

                    leaf vc-type {
                        type enumeration {
                            enum "ether"                        { value 2; }
                            enum "vlan"                         { value 4; }
                        }
                        default "ether";
                        description "Type of virtual circuit (VC) associated with the SDP binding; VPLS not supported";
                    }

                    leaf sdp-type {
                        type enumeration {
                            enum "mesh"                        { value 1; }
                            enum "spoke"                         { value 2; }
                        }
                        default "spoke";
                    }

                    uses sdp-binding-common:sdp-binding-details;
                    container fdb {
                        description "Enter the fdb context";

                        leaf maximum-mac-addresses {
                            type int32 {
                                range "1..511999";
                            }
                            description "Maximum number of MAC entries in the FDB";
                        }

                        leaf discard-unknown-source {
                            type boolean;
                            description "Discard frames with unknown source";
                        }

                        leaf mac-pinning {
                            type boolean;
                            description "Enable MAC address pinning on this SAP";
                        }

                        leaf auto-learn-mac-protect {
                            type boolean;
                            description "Enable automatic update of MAC protect list";
                        }

                        leaf protected-src-mac-violation-action {
                            type enumeration {
                                enum sdp-bind-oper-down             { value 1; }
                                enum alarm-only                     { value 2; }
                                enum discard                        { value 3; }
                            }

                            description "Action when a relearn request for a protected MAC is received on the SDP";
                        }

                        container mac-learning {
                            when "../../sdp-type = 'spoke'";
                            description "Enter the mac-learning context";

                            leaf learning {
                                type boolean;
                                description "Enable learning of new MAC addresses";
                            }

                            leaf aging {
                                type boolean;
                                description "Enable aging of MAC addresses";
                            }
                        } // container mac-learning

                    } // container fdb

                    container igmp-snooping {
                        description "Enter the igmp-snooping context";
                        leaf maximum-number-groups {
                            type uint32 {
                                range "1..16000";
                            }
                            description "Maximum groups allowed";
                        }
                    } // container igmp-snooping
                    leaf control-word {
                        type boolean;
                        description "Use the control word as preferred";
                    }
                    container dhcp {
                        leaf snoop {
                            type boolean;
                            description "Allow DHCP snooping of DHCP messages on the SAP or SDP";
                        }
                    }

                    leaf force-vc-forwarding {
                        type enumeration {
                            enum "vlan"                         { value 1; }
                            enum "qinq-c-tag-c-tag"             { value 2; }
                            enum "qinq-s-tag-c-tag"             { value 3; }
                        }
                        description "VC forwarding action";
                    }
                }
            }
        }
    }
    uses etree:configuration-details;
}
